(defun taz_liczba_pretow ()
  (setq taz_liczba_pretow_p1 (getpoint "\nWskaz poczatkowy punkt rozkladu"))
  (setq taz_liczba_pretow_p2 (getpoint taz_liczba_pretow_p1 "\nWskaz koncowy punkt rozkladu"))  
  
  (setq taz_liczba_pretow_rozstaw (getstring (strcat "\nPodaj rozstaw pretow (mm): <" taz_aktualna_liczba_pretow_rozstaw ">")))
  (if (equal taz_liczba_pretow_rozstaw "")
      (setq taz_liczba_pretow_rozstaw taz_aktualna_liczba_pretow_rozstaw)
      (princ)
  )
  (setq taz_aktualna_liczba_pretow_rozstaw taz_liczba_pretow_rozstaw)
  
  (setq taz_liczba_pretow_odleglosc (distance taz_liczba_pretow_p1 taz_liczba_pretow_p2))
  (setq taz_liczba_pretow_wynik (rtos ((lambda ( taz_liczba_pretow_licznik ) (cond ((equal 0.0 taz_liczba_pretow_licznik 1e-8) (+ (/ taz_liczba_pretow_odleglosc (atoi taz_liczba_pretow_rozstaw)) 1)) ((< (+ (/ taz_liczba_pretow_odleglosc (atoi taz_liczba_pretow_rozstaw)) 1) 0) (- (+ (/ taz_liczba_pretow_odleglosc (atoi taz_liczba_pretow_rozstaw)) 1) taz_liczba_pretow_licznik)) ((+ (+ (/ taz_liczba_pretow_odleglosc (atoi taz_liczba_pretow_rozstaw)) 1) (- 1 taz_liczba_pretow_licznik))))) (rem (+ (/ taz_liczba_pretow_odleglosc (atoi taz_liczba_pretow_rozstaw)) 1) 1))))
  (setq taz_liczba_pretow_dlugosc_rozkladu (rtos (*(- (atoi taz_liczba_pretow_wynik) 1) (atoi taz_liczba_pretow_rozstaw))))
  (princ (strcat "Liczba pretow w rozkladzie wynosi: " taz_liczba_pretow_wynik "\nWymagana dlugosc rozkladu dla tej liczby pretow wynosi: " taz_liczba_pretow_dlugosc_rozkladu " mm"))
  (alert (strcat "Liczba pretow w rozkladzie wynosi: " taz_liczba_pretow_wynik "\nWymagana dlugosc rozkladu dla tej liczby pretow wynosi: " taz_liczba_pretow_dlugosc_rozkladu " mm"))
  (princ)
)

(defun taz_dlugosc_preta ()
  (setq taz_dlugosc_preta_p1 (getpoint "\nWskaz poczatek preta: "))
  (setq taz_dlugosc_preta_p2 (getpoint taz_dlugosc_preta_p1 "\nWskaz koniec preta"))
  
  (setq taz_dlugosc_preta_otulina1 (getstring (strcat "\nPodaj odsuniecie poczatku preta (mm): <" taz_aktualna_dlugosc_preta_otulina1 ">")))
  (if (equal taz_dlugosc_preta_otulina1 "")
      (setq taz_dlugosc_preta_otulina1 taz_aktualna_dlugosc_preta_otulina1)
      (princ)
  )
  (setq taz_aktualna_dlugosc_preta_otulina1 taz_dlugosc_preta_otulina1)
  
  (setq taz_dlugosc_preta_otulina2 (getstring (strcat "\nPodaj odsuniecie konca preta (mm): <" taz_aktualna_dlugosc_preta_otulina2 ">")))
  (if (equal taz_dlugosc_preta_otulina2 "")
      (setq taz_dlugosc_preta_otulina2 taz_aktualna_dlugosc_preta_otulina2)
      (princ)
  )
  (setq taz_aktualna_dlugosc_preta_otulina2 taz_dlugosc_preta_otulina2)
  
  (setq taz_dlugosc_preta_rzeczywista_dl_preta (* 5 (fix (+ (/ (-(-(distance taz_dlugosc_preta_p1 taz_dlugosc_preta_p2) (atoi taz_dlugosc_preta_otulina1))(atoi taz_dlugosc_preta_otulina2)) 5) 0.0001))))
  
  (if (> taz_dlugosc_preta_rzeczywista_dl_preta 12000)
     (setq taz_dlugosc_preta_zbrojeniowego "12000")
     (setq taz_dlugosc_preta_zbrojeniowego (rtos (* 5 (fix (+ (/ (-(-(distance taz_dlugosc_preta_p1 taz_dlugosc_preta_p2) (atoi taz_dlugosc_preta_otulina1))(atoi taz_dlugosc_preta_otulina2)) 5) 0.0001)))))
  )
  
  (setq taz_dlugosc_preta_zbrojeniowego_komunikat (strcat "Maksymalna dlugosc preta wynosi: " taz_dlugosc_preta_zbrojeniowego " mm"))
  
  (princ taz_dlugosc_preta_zbrojeniowego_komunikat)
  (alert taz_dlugosc_preta_zbrojeniowego_komunikat)
  (princ)
)

(defun taz_rozklad( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (setq taz_rozklad_p1 (getpoint "\nWskaz punkt poczatkowy rozkladu: "))
      (setq taz_rozklad_p2 (getpoint taz_rozklad_p1 "\nWskaz punkt koncowy rozkladu: "))
      (command "_dimaligned" taz_rozklad_p1 taz_rozklad_p2 "_T" " " taz_rozklad_p2)
      (vlax-put-property (vlax-ename->vla-object (entlast)) 'Arrowhead1Type 0)
      (vlax-put-property (vlax-ename->vla-object (entlast)) 'Arrowhead2Type 0)
      (vlax-put-property (vlax-ename->vla-object (entlast)) 'ExtLine1Suppress -1)
      (vlax-put-property (vlax-ename->vla-object (entlast)) 'ExtLine2Suppress -1)
      ;(vlax-put-property (vlax-ename->vla-object (entlast)) 'ExtensionLineExtend 0)
      (command "_layer" "_S" taz_aktualna_warstwa "")
    )
  )
  (princ)
)

(defun taz_podzial_rozkladu( / *error* )
  (defun *error* ( taz_przyczyna_bledu )
    (command)(command)
    (command "_layer" "_S" taz_aktualna_warstwa "")
    (princ)
  )
  (setq taz_podzial_rozkladu_odleglosc1 0)
  (setq taz_podzial_rozkladu_odleglosc2 0)
  (setq taz_podzial_rozkladu_rozklad nil)
  (setq taz_aktualna_warstwa (getvar "CLAYER"))
  (command "_layer" "_S" "TAZ_TEXT" "")
  (while (equal taz_podzial_rozkladu_rozklad nil)
    (command)
    (setq taz_podzial_rozkladu_rozklad (car (entsel "Wskaz rozklad: ")))
  )
  (setq taz_podzial_rozkladu_rozklad (entget taz_podzial_rozkladu_rozklad))
  (setq taz_podzial_rozkladu_skala_rozkladu (vlax-get-property (vlax-ename->vla-object (cdr (assoc -1 taz_podzial_rozkladu_rozklad))) 'StyleName))
  (setq taz_podzial_rozkladu_rozstaw_pretow (getreal "Podaj rozstaw pretow (mm): "))
  (setq taz_podzial_rozkladu_p1 (list (cadr (assoc 13 taz_podzial_rozkladu_rozklad)) (caddr (assoc 13 taz_podzial_rozkladu_rozklad)) (cadddr (assoc 13 taz_podzial_rozkladu_rozklad))))
  (setq taz_podzial_rozkladu_p2 (list (cadr (assoc 14 taz_podzial_rozkladu_rozklad)) (caddr (assoc 14 taz_podzial_rozkladu_rozklad)) (cadddr (assoc 14 taz_podzial_rozkladu_rozklad))))
  (setq taz_podzial_rozkladu_p3 (getpoint "Wskaz punkt przeciecia rozkladu: "))
  (command "_ZOOM" "_SCALE" "10000X")
  (setq taz_podzial_rozkladu_a1 (angle taz_podzial_rozkladu_p1 taz_podzial_rozkladu_p2))
  (setq taz_podzial_rozkladu_a2 (angle taz_podzial_rozkladu_p2 taz_podzial_rozkladu_p1))
  (setq taz_podzial_rozkladu_p4 (polar taz_podzial_rozkladu_p1 taz_podzial_rozkladu_a1 (/ (distance taz_podzial_rozkladu_p1 taz_podzial_rozkladu_p2) 2)))
  (command "_ZOOM" "_SCALE" "0.0001X")
  (command "_pline" taz_podzial_rozkladu_p3 (osnap taz_podzial_rozkladu_p4 "_per") "")
  (setq taz_podzial_rozkladu_p5 (list (cadr (assoc 10 (reverse (entget (entlast))))) (caddr (assoc 10 (reverse (entget (entlast))))) (caddr taz_podzial_rozkladu_p3)))
  (command "_erase" (entlast) "")
  (command "_erase" (cdr (assoc -1 taz_podzial_rozkladu_rozklad)) "")
  (while (<= taz_podzial_rozkladu_odleglosc1 (distance taz_podzial_rozkladu_p1 taz_podzial_rozkladu_p5))
    (setq taz_podzial_rozkladu_odleglosc1 (+ taz_podzial_rozkladu_odleglosc1 taz_podzial_rozkladu_rozstaw_pretow))
  )
  (setq taz_podzial_rozkladu_odleglosc1 (- taz_podzial_rozkladu_odleglosc1 taz_podzial_rozkladu_rozstaw_pretow))
  (while (<= taz_podzial_rozkladu_odleglosc2 (distance taz_podzial_rozkladu_p2 taz_podzial_rozkladu_p5))
    (setq taz_podzial_rozkladu_odleglosc2 (+ taz_podzial_rozkladu_odleglosc2 taz_podzial_rozkladu_rozstaw_pretow))
  )
  (setq taz_podzial_rozkladu_odleglosc2 (- taz_podzial_rozkladu_odleglosc2 taz_podzial_rozkladu_rozstaw_pretow))
  (setq taz_podzial_rozkladu_p6 (polar taz_podzial_rozkladu_p1 taz_podzial_rozkladu_a1 taz_podzial_rozkladu_odleglosc1))
  (setq taz_podzial_rozkladu_p7 (polar taz_podzial_rozkladu_p2 taz_podzial_rozkladu_a2 taz_podzial_rozkladu_odleglosc2))
  (command "_dimaligned" taz_podzial_rozkladu_p1 taz_podzial_rozkladu_p6 "_T" " " taz_podzial_rozkladu_p6)
  (vlax-put-property (vlax-ename->vla-object (entlast)) 'StyleName taz_podzial_rozkladu_skala_rozkladu)
  (vlax-put-property (vlax-ename->vla-object (entlast)) 'Arrowhead1Type 0)
  (vlax-put-property (vlax-ename->vla-object (entlast)) 'Arrowhead2Type 0)
  (vlax-put-property (vlax-ename->vla-object (entlast)) 'ExtLine1Suppress -1)
  (vlax-put-property (vlax-ename->vla-object (entlast)) 'ExtLine2Suppress -1)
  (vlax-put-property (vlax-ename->vla-object (entlast)) 'ExtLine2Suppress -1)
  (command "_dimaligned" taz_podzial_rozkladu_p2 taz_podzial_rozkladu_p7 "_T" " " taz_podzial_rozkladu_p7)
  (vlax-put-property (vlax-ename->vla-object (entlast)) 'StyleName taz_podzial_rozkladu_skala_rozkladu)
  (vlax-put-property (vlax-ename->vla-object (entlast)) 'Arrowhead1Type 0)
  (vlax-put-property (vlax-ename->vla-object (entlast)) 'Arrowhead2Type 0)
  (vlax-put-property (vlax-ename->vla-object (entlast)) 'ExtLine1Suppress -1)
  (vlax-put-property (vlax-ename->vla-object (entlast)) 'ExtLine2Suppress -1)
  (command "_layer" "_S" taz_aktualna_warstwa "")
  (princ)
)
