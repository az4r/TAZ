(defun c:taz_pret_skrajny()
  (setq taz_pret_skrajny_pret (car (entsel "\nWybierz pret ktory ma zostac dosuniety do krawedzi: ")))
  (setq taz_pret_skrajny_d1 (cdr (assoc 40 (entget taz_pret_skrajny_pret))))
  (setq taz_pret_skrajny_p1 (cdr (assoc 10 (entget taz_pret_skrajny_pret))))
  (setq taz_pret_skrajny_p2 (getpoint "\nWskaz poczatek luku: "))
  (setq taz_pret_skrajny_p3 (getpoint "\nWskaz koniec luku: "))
  (setq taz_pret_skrajny_p4 (getpoint "\nWskaz srodek luku: "))
  (setq taz_pret_skrajny_d2 (distance taz_pret_skrajny_p2 taz_pret_skrajny_p4))
  (setq taz_pret_skrajny_d3 (/ (* (* 2 PI) taz_pret_skrajny_d2) 16))
  (if (< (car taz_pret_skrajny_p2) (car taz_pret_skrajny_p3))
    (princ)
    (setq taz_pret_skrajny_d3 (* -1 taz_pret_skrajny_d3))
  )
  (command "_arc" "_C" taz_pret_skrajny_p4 taz_pret_skrajny_p2 "_L" taz_pret_skrajny_d3)
  (setq taz_pret_skrajny_p5 (vlax-safearray->list (vlax-variant-value (vla-get-EndPoint (vlax-ename->vla-object (entlast))))))
  (command "_erase" (entlast) "")
  (setq taz_pret_skrajny_a1 (angle taz_pret_skrajny_p5 taz_pret_skrajny_p4))
  (setq taz_pret_skrajny_p6 (polar taz_pret_skrajny_p5 taz_pret_skrajny_a1 taz_pret_skrajny_d1))
  (command "_ZOOM" "_SCALE" "10000X")
  (command "_move" taz_pret_skrajny_pret "" taz_pret_skrajny_p1 taz_pret_skrajny_p6)
  (command "_ZOOM" "_SCALE" "0.0001X")
  (princ)
)
