(defun c:taz_liczba_pretow ()
  (setq taz_aktualna_liczba_pretow_rozstaw "150")
  (setq taz_liczba_pretow_p1 (getpoint "\nWskaz poczatkowy punkt rozkladu"))
  (setq taz_liczba_pretow_p2 (getpoint taz_liczba_pretow_p1 "\nWskaz koncowy punkt rozkladu"))  
  
  (setq taz_liczba_pretow_rozstaw (getstring (strcat "\nPodaj rozstaw pretow (mm): <" taz_aktualna_liczba_pretow_rozstaw ">")))
  (if (equal taz_liczba_pretow_rozstaw "")
      (setq taz_liczba_pretow_rozstaw taz_aktualna_liczba_pretow_rozstaw)
      (princ)
  )
  (setq taz_aktualna_liczba_pretow_rozstaw taz_liczba_pretow_rozstaw)
  
  (setq taz_liczba_pretow_odleglosc (distance taz_liczba_pretow_p1 taz_liczba_pretow_p2))
  (setq taz_liczba_pretow_wynik (rtos ((lambda ( taz_liczba_pretow_licznik ) (cond ((equal 0.0 taz_liczba_pretow_licznik 1e-8) (+ (/ taz_liczba_pretow_odleglosc (atoi taz_liczba_pretow_rozstaw)) 1)) ((< (+ (/ taz_liczba_pretow_odleglosc (atoi taz_liczba_pretow_rozstaw)) 1) 0) (- (+ (/ taz_liczba_pretow_odleglosc (atoi taz_liczba_pretow_rozstaw)) 1) taz_liczba_pretow_licznik)) ((+ (+ (/ taz_liczba_pretow_odleglosc (atoi taz_liczba_pretow_rozstaw)) 1) (- 1 taz_liczba_pretow_licznik))))) (rem (+ (/ taz_liczba_pretow_odleglosc (atoi taz_liczba_pretow_rozstaw)) 1) 1))))
  (setq taz_liczba_pretow_dlugosc_rozkladu (rtos (*(- (atoi taz_liczba_pretow_wynik) 1) (atoi taz_liczba_pretow_rozstaw))))
  (princ (strcat "Liczba pretow w rozkladzie wynosi: " taz_liczba_pretow_wynik "\nWymagana dlugosc rozkladu dla tej liczby pretow wynosi: " taz_liczba_pretow_dlugosc_rozkladu " mm"))
  (alert (strcat "Liczba pretow w rozkladzie wynosi: " taz_liczba_pretow_wynik "\nWymagana dlugosc rozkladu dla tej liczby pretow wynosi: " taz_liczba_pretow_dlugosc_rozkladu " mm"))
  (princ)
)
