(defun taz_warstwa_zero()
  (command "_layer" "_S" "0" "")
  (princ)
)

(defun taz_warstwa_thin()
  (if (tblsearch "LAYER" "TAZ_THIN")
    (command "_layer" "_S" "TAZ_THIN" "")
    (progn
      (taz_wczytaj_warstwy)
      (command "_layer" "_S" "TAZ_THIN" "")
    )
  )
  (princ)
)

(defun taz_warstwa_view()
  (if (tblsearch "LAYER" "TAZ_VIEW")
    (command "_layer" "_S" "TAZ_VIEW" "")
    (progn
      (taz_wczytaj_warstwy)
      (command "_layer" "_S" "TAZ_VIEW" "")
    )
  )
  (princ)
)

(defun taz_warstwa_section()
  (if (tblsearch "LAYER" "TAZ_SECTION")
    (command "_layer" "_S" "TAZ_SECTION" "")
    (progn
      (taz_wczytaj_warstwy)
      (command "_layer" "_S" "TAZ_SECTION" "")
    )
  )
  (princ)
)

(defun taz_warstwa_hidden()
  (if (tblsearch "LAYER" "TAZ_HIDDEN")
    (command "_layer" "_S" "TAZ_HIDDEN" "")
    (progn
      (taz_wczytaj_warstwy)
      (command "_layer" "_S" "TAZ_HIDDEN" "")
    )
  )
  (princ)
)

(defun taz_warstwa_help()
  (if (tblsearch "LAYER" "TAZ_HELP")
    (command "_layer" "_S" "TAZ_HELP" "")
    (progn
      (taz_wczytaj_warstwy)
      (command "_layer" "_S" "TAZ_HELP" "")
    )
  )
  (princ)
)

(defun taz_warstwa_cut()
  (if (tblsearch "LAYER" "TAZ_CUT")
    (command "_layer" "_S" "TAZ_CUT" "")
    (progn
      (taz_wczytaj_warstwy)
      (command "_layer" "_S" "TAZ_CUT" "")
    )
  )
  (princ)
)

(defun taz_warstwa_axis()
  (if (tblsearch "LAYER" "TAZ_AXIS")
    (command "_layer" "_S" "TAZ_AXIS" "")
    (progn
      (taz_wczytaj_warstwy)
      (command "_layer" "_S" "TAZ_AXIS" "")
    )
  )
  (princ)
)

(defun taz_warstwa_hatch()
  (if (tblsearch "LAYER" "TAZ_HATCH")
    (command "_layer" "_S" "TAZ_HATCH" "")
    (progn
      (taz_wczytaj_warstwy)
      (command "_layer" "_S" "TAZ_HATCH" "")
    )
  )
  (princ)
)

(defun taz_przypisz_warstwe( / *error* )
  (defun *error* ( taz_przyczyna_bledu )
    (command)(command)
    (princ)
  )
  (repeat 100
    (setvar "CECOLOR" "BYLAYER")
    (setvar "CELWEIGHT" -1)
    (setvar "CELTYPE" "BYLAYER")
    (setq taz_obiekt_do_zmiany_warstwy (entsel "\nWybierz obiekt do zmiany: "))
    (if (= taz_obiekt_do_zmiany_warstwy nil)
      (taz_przypisz_warstwe)
      (princ)
    )
    (command "_laymch" taz_obiekt_do_zmiany_warstwy "" "" "_Y")
    (setq taz_obiekt_do_zmiany_warstwy (ssadd))
  )
  (princ)
)

(defun taz_przypisz_wlasciwosci( / *error* )
  (defun *error* ( taz_przyczyna_bledu )
    (command)(command)
	(setvar "nomutt" taz_aktualny_tryb_pomijania_komunikatow)
    (princ)
  )
  (setq taz_aktualny_tryb_pomijania_komunikatow (getvar "nomutt"))
  (setq taz_obiekt_zrodlowy_do_przypisania_wlasciwosci (entsel "\nWybierz obiekt zrodlowy: "))
  (prompt "\nWybierz obiekty docelowe: ")
  (setvar "nomutt" 1)
  (setq taz_obiekty_docelowe_do_przypisania_wlasciwosci (ssget))
  (setvar "nomutt" taz_aktualny_tryb_pomijania_komunikatow)
  (command "_matchprop" taz_obiekt_zrodlowy_do_przypisania_wlasciwosci taz_obiekty_docelowe_do_przypisania_wlasciwosci "")
  (princ)
)

(defun taz_skala_1()
  (command "_setvar" "TEXTSTYLE" "TAZ_TS")
  (command "_textsize" "2")
  (command "-dimstyle" "_R" "TAZ_DS_1")
  (command "_setvar" "CMLEADERSTYLE" "TAZ_MLS_1")
  (setq taz_wspolczynnik_skali 1)
  (princ)
)

(defun taz_skala_5()
  (command "_setvar" "TEXTSTYLE" "TAZ_TS")
  (command "_textsize" "10")
  (command "-dimstyle" "_R" "TAZ_DS_5")
  (command "_setvar" "CMLEADERSTYLE" "TAZ_MLS_5")
  (setq taz_wspolczynnik_skali 5)
  (princ)
)

(defun taz_skala_10()
  (command "_setvar" "TEXTSTYLE" "TAZ_TS")
  (command "_textsize" "20")
  (command "-dimstyle" "_R" "TAZ_DS_10")
  (command "_setvar" "CMLEADERSTYLE" "TAZ_MLS_10")
  (setq taz_wspolczynnik_skali 10)
  (princ)
)

(defun taz_skala_20()
  (command "_setvar" "TEXTSTYLE" "TAZ_TS")
  (command "_textsize" "40")
  (command "-dimstyle" "_R" "TAZ_DS_20")
  (command "_setvar" "CMLEADERSTYLE" "TAZ_MLS_20")
  (setq taz_wspolczynnik_skali 20)
  (princ)
)

(defun taz_skala_50()
  (command "_setvar" "TEXTSTYLE" "TAZ_TS")
  (command "_textsize" "100")
  (command "-dimstyle" "_R" "TAZ_DS_50")
  (command "_setvar" "CMLEADERSTYLE" "TAZ_MLS_50")
  (setq taz_wspolczynnik_skali 50)
  (princ)
)

(defun taz_skala_100()
  (command "_setvar" "TEXTSTYLE" "TAZ_TS")
  (command "_textsize" "200")
  (command "-dimstyle" "_R" "TAZ_DS_100")
  (command "_setvar" "CMLEADERSTYLE" "TAZ_MLS_100")
  (setq taz_wspolczynnik_skali 100)
  (princ)
)

(defun taz_skala_200()
  (command "_setvar" "TEXTSTYLE" "TAZ_TS")
  (command "_textsize" "400")
  (command "-dimstyle" "_R" "TAZ_DS_200")
  (command "_setvar" "CMLEADERSTYLE" "TAZ_MLS_200")
  (setq taz_wspolczynnik_skali 200)
  (princ)
)

(defun taz_tekst_maly( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (command "_mtext" (getpoint "\nPodaj punkt wstawienia tekstu: ") "_H" (* taz_wspolczynnik_skali 2) (getvar "lastpoint") "\n" "")
      (command "_mtedit" (entlast))
      (command "_layer" "_S" taz_aktualna_warstwa "")
    )
  )
  (princ)
)

(defun taz_tekst_sredni( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (command "_mtext" (getpoint "\nPodaj punkt wstawienia tekstu: ") "_H" (* taz_wspolczynnik_skali 2.5) (getvar "lastpoint") "\n" "")
      (command "_mtedit" (entlast))
      (command "_layer" "_S" taz_aktualna_warstwa "")
    )
  )
  (princ)
)

(defun taz_tekst_duzy( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (command "_mtext" (getpoint "\nPodaj punkt wstawienia tekstu: ") "_H" (* taz_wspolczynnik_skali 3) (getvar "lastpoint") "\n" "")
      (command "_mtedit" (entlast))
      (command "_layer" "_S" taz_aktualna_warstwa "")
    )
  )
  (princ)
)

(defun taz_strzalka_opisu( / *error* )
  (defun *error* ( taz_przyczyna_bledu )
    (command)(command)
    (princ)
  )
  (if (equal taz_wspolczynnik_skali nil)
    (print "Najpierw wybierz skale")
    (progn
      (setq taz_aktualna_warstwa (getvar "CLAYER"))
      (setq taz_strzalka_opisu_p1 (getpoint "\nWskaz pierwszy punkt dla strzalki opisu: "))
      (setq taz_strzalka_opisu_p2 (getpoint taz_strzalka_opisu_p1 "\nWskaz drugi punkt dla strzalki opisu: "))
      (setq taz_strzalka_opisu_tekst (getstring "\nPodaj tekst dla strzalki opisu: "))
      (command "_layer" "_S" "TAZ_TEXT" "")
      (command "_mleader" taz_strzalka_opisu_p1 taz_strzalka_opisu_p2 "" taz_strzalka_opisu_tekst)
      (setq taz_strzalka_opisu_p1 (ssadd))
      (setq taz_strzalka_opisu_p2 (ssadd))
      (setq taz_strzalka_opisu_tekst (ssadd))
      (command "_layer" "_S" taz_aktualna_warstwa "")
    )
  )
  (princ)
)

(defun taz_wymiar_liniowy( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (command "_dimlinear" (getpoint "\nWskaz pierwszy punkt dla wymiaru: ") (getpoint "\nWskaz drugi punkt dla wymiaru: ") (getpoint "\nWskaz miejsce polozenia linii wymiarowej: "))
      (command "_layer" "_S" taz_aktualna_warstwa "")
    )
  )
  (princ)
)

(defun taz_wymiar_wyrownany( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (command "_dimaligned" (getpoint "\nWskaz pierwszy punkt dla wymiaru: ") (getpoint "\nWskaz drugi punkt dla wymiaru: ") (getpoint "\nWskaz miejsce polozenia linii wymiarowej: "))
      (command "_layer" "_S" taz_aktualna_warstwa "")
    )
  )
  (princ)
)

(defun taz_kontynuuj_wymiar( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (setq taz_kontynuuj_wymiar_obiekt (entsel "\nWybierz wymiar do kontynuacji: "))
      (repeat 100
        (setq taz_kontynuuj_wymiar_p1 (getpoint "\nWskaz kolejny punkt dla wymiaru: "))
        (command "_dimcontinue" taz_kontynuuj_wymiar_obiekt taz_kontynuuj_wymiar_p1)
      )
      ;(while (> (getvar 'cmdactive) 0) (command pause))
      ;(command "_layer" "_S" taz_aktualna_warstwa "")
    )
  )
  (princ)
)

(defun taz_przetnij_w_punkcie( / *error* )
  (defun *error* ( taz_przyczyna_bledu )
    (command)
    (princ)
  )
  (repeat 100
    (setq taz_przetnij_w_punkcie_obiekt (entsel "\nWskaz obiekt do przeciecia: "))
    (setq taz_przetnij_w_punkcie_p1 (getpoint "\nWskaz punkt przeciecia: "))
    (command "_break" taz_przetnij_w_punkcie_obiekt "_F" taz_przetnij_w_punkcie_p1 taz_przetnij_w_punkcie_p1)
  )
  (princ)
)

(defun taz_przytnij_do_punktu( / *error* )
  (defun *error* ( taz_przyczyna_bledu )
    (command)
    (princ)
  )
  (repeat 100
    (setq taz_przytnij_do_punktu_obiekt (entsel "\nWskaz obiekt do przyciecia/wydluzenia: "))
    (setq taz_przytnij_do_punktu_p1 (getpoint "\nWskaz punkt docelowy: "))
    (command "_lengthen" "_DY" taz_przytnij_do_punktu_obiekt taz_przytnij_do_punktu_p1 "")
  )
  (princ)
)

(defun taz_wydluz( / *error* )
  (defun *error* ( taz_przyczyna_bledu )
    (command)
    (princ)
  )
  (if (equal taz_wspolczynnik_skali nil)
    (print "Najpierw wybierz skale")
    (progn
      (repeat 100
        (setq taz_wydluz_obiekt (entsel "\nWskaz obiekt do wydluzenia: "))
        (command "_lengthen" "_DE" (* 3 taz_wspolczynnik_skali) taz_wydluz_obiekt "")
      )
    )
  )
  (princ)
)

(defun taz_kreskowanie( / *error* )
  (defun *error* ( taz_przyczyna_bledu )
    (command)(command)
    (command "_setvar" "HPNAME" taz_aktualny_wzor_kreskowania)
    (princ)
  )
  (setq taz_aktualny_wzor_kreskowania (getvar "HPNAME"))
  (repeat 100
    (command "_setvar" "HPNAME" "SOLID")
    (setq taz_kreskowanie_p1 (getpoint "\nWskaz punkt wewnatrz obszaru do zakreskowania: "))
    (command "_bhatch" taz_kreskowanie_p1 "")
    (command "_setvar" "HPNAME" taz_aktualny_wzor_kreskowania)
  )
  (princ)
)

(defun taz_symbol_przekroju( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (setq taz_symbol_przekroju_p1 (getpoint "\nWskaz pierwszy punkt dla prekroju: "))
      (setq taz_symbol_przekroju_p2 (getpoint taz_symbol_przekroju_p1 "\nWskaz drugi punkt dla prekroju: "))
      (setq taz_symbol_przekroju_a1 (* (angle taz_symbol_przekroju_p1 taz_symbol_przekroju_p2) (/ 180 PI)))
      (setq taz_symbol_przekroju_p3 (polar taz_symbol_przekroju_p1 (/ (- taz_symbol_przekroju_a1 90) (/ 180 PI)) (* 10 taz_wspolczynnik_skali)))
      (setq taz_symbol_przekroju_p4 (polar taz_symbol_przekroju_p1 (/ (- taz_symbol_przekroju_a1 90) (/ 180 PI)) (* 4 taz_wspolczynnik_skali)))
      (setq taz_symbol_przekroju_p5 (polar taz_symbol_przekroju_p4 (/ (- taz_symbol_przekroju_a1 180) (/ 180 PI)) (* 3 taz_wspolczynnik_skali)))
      (setq taz_symbol_przekroju_p6 (polar taz_symbol_przekroju_p4 (/ taz_symbol_przekroju_a1 (/ 180 PI)) (* 3 taz_wspolczynnik_skali)))
      (setq taz_symbol_przekroju_p7 (polar taz_symbol_przekroju_p1 (/ (- taz_symbol_przekroju_a1 110) (/ 180 PI)) (* 8 taz_wspolczynnik_skali)))
      (setq taz_symbol_przekroju_p8 (polar taz_symbol_przekroju_p2 (/ (- taz_symbol_przekroju_a1 90) (/ 180 PI)) (* 10 taz_wspolczynnik_skali)))
      (setq taz_symbol_przekroju_p9 (polar taz_symbol_przekroju_p2 (/ (- taz_symbol_przekroju_a1 90) (/ 180 PI)) (* 4 taz_wspolczynnik_skali)))
      (setq taz_symbol_przekroju_p10 (polar taz_symbol_przekroju_p9 (/ (- taz_symbol_przekroju_a1 180) (/ 180 PI)) (* 3 taz_wspolczynnik_skali)))
      (setq taz_symbol_przekroju_p11 (polar taz_symbol_przekroju_p9 (/ taz_symbol_przekroju_a1 (/ 180 PI)) (* 3 taz_wspolczynnik_skali)))
      (setq taz_symbol_przekroju_p12 (polar taz_symbol_przekroju_p2 (/ (- taz_symbol_przekroju_a1 70) (/ 180 PI)) (* 8 taz_wspolczynnik_skali)))
      (setq taz_symbol_przekroju_p13 (getpoint "\nWskaz kierunek patrzenia: "))
      (setq taz_oznaczenie_przekroju (getstring "\nPodaj oznaczenie dla przekroju: "))
      (setq taz_symbol_przekroju_scalenie (ssadd))
      (command "_ZOOM" "_SCALE" "10000X")
      (command "_pline" taz_symbol_przekroju_p3 taz_symbol_przekroju_p1 taz_symbol_przekroju_p5 taz_symbol_przekroju_p6 "")
      (ssadd (entlast) taz_symbol_przekroju_scalenie)
      (command "_text" "_J" "_M" taz_symbol_przekroju_p7 (* taz_wspolczynnik_skali 2.5) "0" taz_oznaczenie_przekroju)
      (setq taz_oznaczenie_przekroju_txt1 (entlast))
      (ssadd (entlast) taz_symbol_przekroju_scalenie)
      (command "_pline" taz_symbol_przekroju_p8 taz_symbol_przekroju_p2 taz_symbol_przekroju_p11 taz_symbol_przekroju_p10 "")
      (ssadd (entlast) taz_symbol_przekroju_scalenie)
      (command "_text" "_J" "_M" taz_symbol_przekroju_p12 (* taz_wspolczynnik_skali 2.5) "0" taz_oznaczenie_przekroju)
      (setq taz_oznaczenie_przekroju_txt2 (entlast))
      (ssadd (entlast) taz_symbol_przekroju_scalenie)
      (if (< (distance taz_symbol_przekroju_p1 taz_symbol_przekroju_p13) (distance taz_symbol_przekroju_p3 taz_symbol_przekroju_p13))
        (progn
		  (command "_group" "_C" "*" "" taz_symbol_przekroju_scalenie "")
		  (setq taz_symbol_przekroju_scalenie (ssadd))
		)
        (progn
          (command "_mirror" taz_symbol_przekroju_scalenie "" taz_symbol_przekroju_p1 taz_symbol_przekroju_p2 "_Y")
          (setpropertyvalue taz_oznaczenie_przekroju_txt1 "Rotation" 0)
          (setpropertyvalue taz_oznaczenie_przekroju_txt2 "Rotation" 0)
        )
      )
      (command "_ZOOM" "_SCALE" "0.0001X")
	  (command "_group" "_C" "*" "" taz_symbol_przekroju_scalenie "")
      (setq taz_symbol_przekroju_scalenie (ssadd))
      (command "_layer" "_S" taz_aktualna_warstwa "")
    )
  )
  (princ)
)

(defun taz_opis_dwuliniowy( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (setq taz_opis_dwuliniowy_txt1 (getstring "\nPodaj pierwszy opis: "))
      (setq taz_opis_dwuliniowy_txt2 (getstring "\nPodaj drugi opis: "))
      (setq taz_opis_dwuliniowy_txt3 (getstring "\nPodaj skale: "))
      (setq taz_opis_dwuliniowy_p1 (getpoint "\nPodaj punkt wstawienia opisu: "))
      (setq taz_opis_dwuliniowy_p2 (polar taz_opis_dwuliniowy_p1 (/ 90 (/ 180 PI)) (* taz_wspolczynnik_skali 5)))
      (setq taz_opis_dwuliniowy_p3 (polar taz_opis_dwuliniowy_p1 (/ 90 (/ 180 PI)) (* taz_wspolczynnik_skali 1.75)))
      (setq taz_opis_dwuliniowy_p4 (polar taz_opis_dwuliniowy_p1 (/ 270 (/ 180 PI)) (* taz_wspolczynnik_skali 1.75)))
      (setq taz_opis_dwuliniowy_p5 (polar taz_opis_dwuliniowy_p1 (/ 180 (/ 180 PI)) (* taz_wspolczynnik_skali 5)))
      (setq taz_opis_dwuliniowy_p6 (polar taz_opis_dwuliniowy_p1 (/ 0 (/ 180 PI)) (* taz_wspolczynnik_skali 5)))
      (setq taz_opis_dwuliniowy_scalenie (ssadd))
      (command "_ZOOM" "_SCALE" "10000X")
      (command "_text" "_J" "_M" taz_opis_dwuliniowy_p2 (* taz_wspolczynnik_skali 3) "0" taz_opis_dwuliniowy_txt1)
      (ssadd (entlast) taz_opis_dwuliniowy_scalenie)
      (command "_text" "_J" "_M" taz_opis_dwuliniowy_p3 (* taz_wspolczynnik_skali 2.5) "0" taz_opis_dwuliniowy_txt2)
      (ssadd (entlast) taz_opis_dwuliniowy_scalenie)
      (command "_text" "_J" "_M" taz_opis_dwuliniowy_p4 (* taz_wspolczynnik_skali 2.5) "0" taz_opis_dwuliniowy_txt3)
      (ssadd (entlast) taz_opis_dwuliniowy_scalenie)
      (command "_pline" taz_opis_dwuliniowy_p5 taz_opis_dwuliniowy_p6 "")
      (ssadd (entlast) taz_opis_dwuliniowy_scalenie)
      (command "_ZOOM" "_SCALE" "0.0001X")
      (command "_group" "_C" "*" "" taz_opis_dwuliniowy_scalenie "")
      (setq taz_opis_dwuliniowy_scalenie (ssadd))
      (command "_layer" "_S" taz_aktualna_warstwa "")
    )
  )
  (princ)
)

(defun taz_opis_jednoliniowy( / *error* )
  (defun *error* ( taz_przyczyna_bledu )
    (command)(command)
    (command "_layer" "_S" taz_aktualna_warstwa "")
    (princ)
  )
  (if (equal taz_wspolczynnik_skali nil)
    (print "Najpierw wybierz skale")
    (progn
      (setq taz_aktualna_warstwa (getvar "CLAYER"))
      (command "_layer" "_S" "TAZ_TEXT" "")
      (setq taz_opis_jednoliniowy_txt1 (getstring "\nPodaj opis: "))
      (setq taz_opis_jednoliniowy_txt2 (getstring "\nPodaj skale: "))
      (setq taz_opis_jednoliniowy_p1 (getpoint "\nPodaj punkt wstawienia opisu: "))
      (setq taz_opis_jednoliniowy_p2 (polar taz_opis_jednoliniowy_p1 (/ 90 (/ 180 PI)) (* taz_wspolczynnik_skali 2.3)))
      (setq taz_opis_jednoliniowy_p3 (polar taz_opis_jednoliniowy_p1 (/ 270 (/ 180 PI)) (* taz_wspolczynnik_skali 1.75)))
      (setq taz_opis_jednoliniowy_p4 (polar taz_opis_jednoliniowy_p1 (/ 180 (/ 180 PI)) (* taz_wspolczynnik_skali 5)))
      (setq taz_opis_jednoliniowy_p5 (polar taz_opis_jednoliniowy_p1 (/ 0 (/ 180 PI)) (* taz_wspolczynnik_skali 5)))
      (setq taz_opis_jednoliniowy_scalenie (ssadd))
      (command "_ZOOM" "_SCALE" "10000X")
      (command "_text" "_J" "_M" taz_opis_jednoliniowy_p2 (* taz_wspolczynnik_skali 3) "0" taz_opis_jednoliniowy_txt1)
      (ssadd (entlast) taz_opis_jednoliniowy_scalenie)
      (command "_text" "_J" "_M" taz_opis_jednoliniowy_p3 (* taz_wspolczynnik_skali 2.5) "0" taz_opis_jednoliniowy_txt2)
      (ssadd (entlast) taz_opis_jednoliniowy_scalenie)
      (command "_pline" taz_opis_jednoliniowy_p4 taz_opis_jednoliniowy_p5 "")
      (ssadd (entlast) taz_opis_jednoliniowy_scalenie)
      (command "_ZOOM" "_SCALE" "0.0001X")
      (command "_group" "_C" "*" "" taz_opis_jednoliniowy_scalenie "")
      (setq taz_opis_jednoliniowy_scalenie (ssadd))
      (command "_layer" "_S" taz_aktualna_warstwa "")
    )
  )
  (princ)
)

(defun taz_kota_gora( / *error* )
  (defun *error* ( taz_przyczyna_bledu )
    (command)(command)
	(command "_UCS" "_P")
    (command "_layer" "_S" taz_aktualna_warstwa "")
    (setvar "pickstyle" taz_aktualny_wybor_grup)
    (setvar "orthomode" taz_aktualny_tryb_orto)
    (setvar "dimzin" taz_aktualny_tryb_pomijania_zer)
	(setvar "nomutt" taz_aktualny_tryb_pomijania_komunikatow)
    (princ)
  )
  (if (equal taz_wspolczynnik_skali nil)
    (print "Najpierw wybierz skale")
    (progn
      (setq taz_aktualna_warstwa (getvar "CLAYER"))
      (setq taz_aktualny_wybor_grup (getvar "pickstyle"))
      (setq taz_aktualny_tryb_orto (getvar "orthomode"))
      (setq taz_aktualny_tryb_pomijania_zer (getvar "dimzin"))
	  (setq taz_aktualny_tryb_pomijania_komunikatow (getvar "nomutt"))
	  (command "_UCS" "_W")
      (command "_layer" "_S" "TAZ_TEXT" "")
      (setvar "pickstyle" 1)
      (setvar "orthomode" 1)
      (setvar "dimzin" 0)
      (setq taz_kota_gora_p1 (getpoint "\nWskaz punkt zaczepienia koty wysokosciowej: "))
      (setq taz_kota_gora_p2 (getpoint taz_kota_gora_p1 "\nWskaz punkt wstawienia symbolu koty wysokosciowej: "))
      (prompt "\nWskaz kote odniesienia lub nacisnij ENTER: ")
	  (setvar "nomutt" 1)
      (setq taz_kota_gora_kota_odniesienia (ssget "_:S"))
	  (setvar "nomutt" taz_aktualny_tryb_pomijania_komunikatow)
      (setq taz_kota_gora_a1 (* (angle taz_kota_gora_p1 taz_kota_gora_p2) (/ 180 PI)))
      (if (> taz_kota_gora_a1 0)
        (progn
          (setq taz_kota_gora_operator -)
          (setq taz_kota_gora_wyrownanie "_BR")
        )
        (progn
          (setq taz_kota_gora_operator +)
          (setq taz_kota_gora_wyrownanie "_BL")
        )
      )
      (setq taz_kota_gora_p3 (polar taz_kota_gora_p2 (/ (taz_kota_gora_operator taz_kota_gora_a1 90) (/ 180 PI)) (* 3 taz_wspolczynnik_skali)))
      (setq taz_kota_gora_p4 (polar taz_kota_gora_p3 (/ (taz_kota_gora_operator taz_kota_gora_a1 180) (/ 180 PI)) (* 3 taz_wspolczynnik_skali)))
      (setq taz_kota_gora_p5 (polar taz_kota_gora_p3 (/ (taz_kota_gora_operator taz_kota_gora_a1 0) (/ 180 PI)) (* 12 taz_wspolczynnik_skali)))
      (setq taz_kota_gora_p6 (polar taz_kota_gora_p2 (/ (taz_kota_gora_operator taz_kota_gora_a1 90) (/ 180 PI)) (* 7 taz_wspolczynnik_skali)))
      (setq taz_kota_gora_p7 (polar taz_kota_gora_p3 (/ (taz_kota_gora_operator taz_kota_gora_a1 45) (/ 180 PI)) (* 1 taz_wspolczynnik_skali)))
      (setq taz_kota_gora_scalenie (ssadd))
      (if (= taz_kota_gora_kota_odniesienia nil)
        (setq taz_kota_gora_poziom (getstring (strcat "\nPodaj poziom: <" taz_kota_gora_aktualny_poziom ">")))
        (progn
          (setq taz_kota_gora_kota_odniesienia_poziom (ssget "P" '((0 . "text"))))
          (setq taz_kota_gora_kota_odniesienia_punkt (ssdel (ssname taz_kota_gora_kota_odniesienia_poziom 0) taz_kota_gora_kota_odniesienia))
          (setq taz_kota_gora_kota_odniesienia_poziom (cdr (assoc 1 (entget (ssname taz_kota_gora_kota_odniesienia_poziom 0)))))
          (setq taz_kota_gora_kota_odniesienia_punkt (cddr (nth 22 (entget (ssname taz_kota_gora_kota_odniesienia_punkt 0)))))
          (setq taz_kota_gora_kota_odniesienia_punkt (car taz_kota_gora_kota_odniesienia_punkt))
          (setq taz_kota_gora_poziom (/ (- (cadr taz_kota_gora_p1) taz_kota_gora_kota_odniesienia_punkt) 1000))
          (setq taz_kota_gora_poziom (rtos (+ taz_kota_gora_poziom (atof taz_kota_gora_kota_odniesienia_poziom)) 2 3))
        )
      )
      (if (equal taz_kota_gora_poziom "")
        (setq taz_kota_gora_poziom taz_kota_gora_aktualny_poziom)
        (princ)
      )
      (command "_ZOOM" "_SCALE" "10000X")
      (command "_pline" taz_kota_gora_p1 taz_kota_gora_p2 "")
      (command "_solid" taz_kota_gora_p2 taz_kota_gora_p3 taz_kota_gora_p4 "" "")
      (command "_pline" taz_kota_gora_p6 taz_kota_gora_p2 taz_kota_gora_p4 taz_kota_gora_p5 "")
      (ssadd (entlast) taz_kota_gora_scalenie)
      (command "_text" "_J" taz_kota_gora_wyrownanie taz_kota_gora_p7 (* taz_wspolczynnik_skali 2) "0" taz_kota_gora_poziom)
      (ssadd (entlast) taz_kota_gora_scalenie)
      (command "_ZOOM" "_SCALE" "0.0001X")
      (command "_group" "_C" "*" "" taz_kota_gora_scalenie "")
      (setq taz_kota_gora_scalenie (ssadd))
	  (command "_UCS" "_P")
      (command "_layer" "_S" taz_aktualna_warstwa "")
      (setvar "pickstyle" taz_aktualny_wybor_grup)
      (setvar "orthomode" taz_aktualny_tryb_orto)
      (setvar "dimzin" taz_aktualny_tryb_pomijania_zer)
    )
  )
  (princ)
)

(defun taz_kota_dol( / *error* )
  (defun *error* ( taz_przyczyna_bledu )
    (command)(command)
	(command "_UCS" "_P")
    (command "_layer" "_S" taz_aktualna_warstwa "")
    (setvar "pickstyle" taz_aktualny_wybor_grup)
    (setvar "orthomode" taz_aktualny_tryb_orto)
    (setvar "dimzin" taz_aktualny_tryb_pomijania_zer)
	(setvar "nomutt" taz_aktualny_tryb_pomijania_komunikatow)
    (princ)
  )
  (if (equal taz_wspolczynnik_skali nil)
    (print "Najpierw wybierz skale")
    (progn
      (setq taz_aktualna_warstwa (getvar "CLAYER"))
      (setq taz_aktualny_wybor_grup (getvar "pickstyle"))
      (setq taz_aktualny_tryb_orto (getvar "orthomode"))
      (setq taz_aktualny_tryb_pomijania_zer (getvar "dimzin"))
	  (setq taz_aktualny_tryb_pomijania_komunikatow (getvar "nomutt"))
	  (command "_UCS" "_W")
      (command "_layer" "_S" "TAZ_TEXT" "")
      (setvar "pickstyle" 1)
      (setvar "orthomode" 1)
      (setvar "dimzin" 0)
      (setq taz_kota_dol_p1 (getpoint "\nWskaz punkt zaczepienia koty wysokosciowej: "))
      (setq taz_kota_dol_p2 (getpoint taz_kota_dol_p1 "\nWskaz punkt wstawienia symbolu koty wysokosciowej: "))
      (prompt "\nWskaz kote odniesienia lub nacisnij ENTER: ")
	  (setvar "nomutt" 1)
      (setq taz_kota_dol_kota_odniesienia (ssget "_:S"))
	  (setvar "nomutt" taz_aktualny_tryb_pomijania_komunikatow)
      (setq taz_kota_dol_a1 (* (angle taz_kota_dol_p1 taz_kota_dol_p2) (/ 180 PI)))
      (if (> taz_kota_dol_a1 0)
        (progn
          (setq taz_kota_dol_operator +)
          (setq taz_kota_dol_wyrownanie "_TR")
        )
        (progn
          (setq taz_kota_dol_operator -)
          (setq taz_kota_dol_wyrownanie "_TL")
        )
      )
      (setq taz_kota_dol_p3 (polar taz_kota_dol_p2 (/ (taz_kota_dol_operator taz_kota_dol_a1 90) (/ 180 PI)) (* 3 taz_wspolczynnik_skali)))
      (setq taz_kota_dol_p4 (polar taz_kota_dol_p3 (/ (taz_kota_dol_operator taz_kota_dol_a1 180) (/ 180 PI)) (* 3 taz_wspolczynnik_skali)))
      (setq taz_kota_dol_p5 (polar taz_kota_dol_p3 (/ (taz_kota_dol_operator taz_kota_dol_a1 0) (/ 180 PI)) (* 12 taz_wspolczynnik_skali)))
      (setq taz_kota_dol_p6 (polar taz_kota_dol_p2 (/ (taz_kota_dol_operator taz_kota_dol_a1 90) (/ 180 PI)) (* 7 taz_wspolczynnik_skali)))
      (setq taz_kota_dol_p7 (polar taz_kota_dol_p3 (/ (taz_kota_dol_operator taz_kota_dol_a1 45) (/ 180 PI)) (* 1 taz_wspolczynnik_skali)))
      (setq taz_kota_dol_scalenie (ssadd))
      (if (= taz_kota_dol_kota_odniesienia nil)
        (setq taz_kota_dol_poziom (getstring (strcat "\nPodaj poziom: <" taz_kota_dol_aktualny_poziom ">")))
        (progn
          (setq taz_kota_dol_kota_odniesienia_poziom (ssget "P" '((0 . "text"))))
          (setq taz_kota_dol_kota_odniesienia_punkt (ssdel (ssname taz_kota_dol_kota_odniesienia_poziom 0) taz_kota_dol_kota_odniesienia))
          (setq taz_kota_dol_kota_odniesienia_poziom (cdr (assoc 1 (entget (ssname taz_kota_dol_kota_odniesienia_poziom 0)))))
          (setq taz_kota_dol_kota_odniesienia_punkt (cddr (nth 22 (entget (ssname taz_kota_dol_kota_odniesienia_punkt 0)))))
          (setq taz_kota_dol_kota_odniesienia_punkt (car taz_kota_dol_kota_odniesienia_punkt))
          (setq taz_kota_dol_poziom (/ (- (cadr taz_kota_dol_p1) taz_kota_dol_kota_odniesienia_punkt) 1000))
          (setq taz_kota_dol_poziom (rtos (+ taz_kota_dol_poziom (atof taz_kota_dol_kota_odniesienia_poziom)) 2 3))
        )
      )
      (if (equal taz_kota_dol_poziom "")
        (setq taz_kota_dol_poziom taz_kota_dol_aktualny_poziom)
        (princ)
      )
      (command "_ZOOM" "_SCALE" "10000X")
      (command "_pline" taz_kota_dol_p1 taz_kota_dol_p2 "")
      (command "_solid" taz_kota_dol_p2 taz_kota_dol_p3 taz_kota_dol_p4 "" "")
      (command "_pline" taz_kota_dol_p6 taz_kota_dol_p2 taz_kota_dol_p4 taz_kota_dol_p5 "")
      (ssadd (entlast) taz_kota_dol_scalenie)
      (command "_text" "_J" taz_kota_dol_wyrownanie taz_kota_dol_p7 (* taz_wspolczynnik_skali 2) "0" taz_kota_dol_poziom)
      (ssadd (entlast) taz_kota_dol_scalenie)
      (command "_ZOOM" "_SCALE" "0.0001X")
      (command "_group" "_C" "*" "" taz_kota_dol_scalenie "")
      (setq taz_kota_dol_scalenie (ssadd))
	  (command "_UCS" "_P")
      (command "_layer" "_S" taz_aktualna_warstwa "")
      (setvar "pickstyle" taz_aktualny_wybor_grup)
      (setvar "orthomode" taz_aktualny_tryb_orto)
      (setvar "dimzin" taz_aktualny_tryb_pomijania_zer)
    )
  )
  (princ)
)

(defun taz_detal( / *error* )
  (defun *error* ( taz_przyczyna_bledu )
    (command)(command)
    (setq taz_detal_scalenie (ssadd))
	(command "_UCS" "_P")
    (command "_layer" "_S" taz_aktualna_warstwa "")
    (princ)
  )
  (if (equal taz_wspolczynnik_skali nil)
    (print "Najpierw wybierz skale")
    (progn
      (setq taz_aktualna_warstwa (getvar "CLAYER"))
	  (command "_UCS" "_W")
      (command "_layer" "_S" "TAZ_TEXT" "")
      (setq taz_detal_p1 (getpoint "\nWskaz pierwszy punkt ramki detalu: "))
      (setq taz_detal_p2 (getcorner taz_detal_p1 "\nWskaz drugi punkt ramki detalu: "))
      (setq taz_detal_p3 (list (car taz_detal_p1) (cadr taz_detal_p2) (caddr taz_detal_p1)))
      (setq taz_detal_p4 (list (car taz_detal_p2) (cadr taz_detal_p1) (caddr taz_detal_p1)))
      (setq taz_detal_a1 (* (angle taz_detal_p1 taz_detal_p4) (/ 180 PI)))
      (setq taz_detal_promien_zaokraglenia (* 3 taz_wspolczynnik_skali))
      (setq taz_detal_odleglosc_wydluzenia (- (* taz_detal_promien_zaokraglenia (sqrt 2)) taz_detal_promien_zaokraglenia))
      (if (and (equal taz_detal_a1 0) (equal (* (angle taz_detal_p1 taz_detal_p3) (/ 180 PI)) 270))
        (setq taz_detal_operator -)
        (princ)
      )
      (if (and (/= taz_detal_a1 0) (equal (* (angle taz_detal_p1 taz_detal_p3) (/ 180 PI)) 270))
        (setq taz_detal_operator +)
        (princ)
      )
      (if (and (equal taz_detal_a1 0) (/= (* (angle taz_detal_p1 taz_detal_p3) (/ 180 PI)) 270))
        (setq taz_detal_operator +)
        (princ)
      )
      (if (and (/= taz_detal_a1 0) (/= (* (angle taz_detal_p1 taz_detal_p3) (/ 180 PI)) 270))
        (setq taz_detal_operator -)
        (princ)
      )
      (setq taz_detal_p5 (polar taz_detal_p1 (/ (taz_detal_operator taz_detal_a1 45) (/ 180 PI)) taz_detal_odleglosc_wydluzenia))
      (setq taz_detal_p6 (polar taz_detal_p2 (/ (taz_detal_operator taz_detal_a1 225) (/ 180 PI)) taz_detal_odleglosc_wydluzenia))
      (setq taz_detal_p7 (polar taz_detal_p3 (/ (taz_detal_operator taz_detal_a1 315) (/ 180 PI)) taz_detal_odleglosc_wydluzenia))
      (setq taz_detal_p8 (polar taz_detal_p4 (/ (taz_detal_operator taz_detal_a1 135) (/ 180 PI)) taz_detal_odleglosc_wydluzenia))
      (setq taz_detal_scalenie (ssadd))
      (command "_ZOOM" "_SCALE" "10000X")
      (command "_rectang" "_F" taz_detal_promien_zaokraglenia taz_detal_p1 taz_detal_p2)
	  (vlax-put-property (vlax-ename->vla-object (entlast)) 'Linetype "DASHED")
	  (vlax-put-property (vlax-ename->vla-object (entlast)) 'LinetypeScale (/ (float 1) taz_wspolczynnik_skali))
      (ssadd (entlast) taz_detal_scalenie)
      (command "_ZOOM" "_SCALE" "0.0001X")
      (setq taz_detal_p9 (getpoint "\nWskaz punkt oznaczenia detalu: "))
      (setq taz_oznaczenie_detalu (getstring "\nPodaj oznaczenie dla detalu: "))
      (setq taz_detal_odleglosc_od_krawedzi (min (distance taz_detal_p9 taz_detal_p5) (distance taz_detal_p9 taz_detal_p6) (distance taz_detal_p9 taz_detal_p7) (distance taz_detal_p9 taz_detal_p8)))
      (if (equal taz_detal_odleglosc_od_krawedzi (distance taz_detal_p9 taz_detal_p5))
        (setq taz_detal_p10 taz_detal_p5)
        (princ)
      )
      (if (equal taz_detal_odleglosc_od_krawedzi (distance taz_detal_p9 taz_detal_p6))
        (setq taz_detal_p10 taz_detal_p6)
        (princ)
      )
      (if (equal taz_detal_odleglosc_od_krawedzi (distance taz_detal_p9 taz_detal_p7))
        (setq taz_detal_p10 taz_detal_p7)
        (princ)
      )
      (if (equal taz_detal_odleglosc_od_krawedzi (distance taz_detal_p9 taz_detal_p8))
        (setq taz_detal_p10 taz_detal_p8)
        (princ)
      )
      (command "_ZOOM" "_SCALE" "10000X")
      (command "_mleader" taz_detal_p10 taz_detal_p9 "" taz_oznaczenie_detalu)
      (vlax-put-property (vlax-ename->vla-object (entlast)) 'ArrowheadType 19)
      (ssadd (entlast) taz_detal_scalenie)
      (command "_ZOOM" "_SCALE" "0.0001X")
      (command "_group" "_C" "*" "" taz_detal_scalenie "")
      (setq taz_detal_scalenie (ssadd))
	  (command "_UCS" "_P")
      (command "_layer" "_S" taz_aktualna_warstwa "")
    )
  )
  (princ)
)

(defun taz_chudziak( / *error* )
  (defun *error* ( taz_przyczyna_bledu )
    (command)(command)
    (setq taz_chudziak_scalenie (ssadd))
    (command "_UCS" "_P")
    (command "_layer" "_S" taz_aktualna_warstwa "")
    (setvar "orthomode" taz_aktualny_tryb_orto)
    (princ)
  )
  (command "_UCS" "_W")
  (setq taz_aktualna_warstwa (getvar "CLAYER"))
  (setq taz_aktualny_tryb_orto (getvar "orthomode"))
  (command "_layer" "_S" "TAZ_HATCH" "")
  (setvar "orthomode" 1)
  (setq taz_chudziak_p1 (getpoint "\nWskaz pierwszy punkt dla podlewki: "))
  (setq taz_chudziak_p2 (getpoint taz_chudziak_p1 "\nWskaz drugi punkt dla podlewki: "))
  (setq taz_chudziak_a1 (* (angle taz_chudziak_p1 taz_chudziak_p2) (/ 180 PI)))
  (setq taz_chudziak_grubosc (getreal "\nPodaj grubosc podlewki (mm): "))
  (setq taz_chudziak_wystep (sqrt (+ (expt taz_chudziak_grubosc 2) (expt taz_chudziak_grubosc 2))))
  (if (equal taz_chudziak_a1 0)
    (setq taz_chudziak_operator -)
    (setq taz_chudziak_operator +)
  )
  (setq taz_chudziak_p3 (polar taz_chudziak_p2 (/ (taz_chudziak_operator taz_chudziak_a1 45) (/ 180 PI)) taz_chudziak_wystep))
  (setq taz_chudziak_p4 (polar taz_chudziak_p1 (/ (taz_chudziak_operator taz_chudziak_a1 135) (/ 180 PI)) taz_chudziak_wystep))
  (setq taz_chudziak_scalenie (ssadd))
  (command "_ZOOM" "_SCALE" "10000X")
  (command "_pline" taz_chudziak_p1 taz_chudziak_p2 taz_chudziak_p3 taz_chudziak_p4 taz_chudziak_p1 "")
  (ssadd (entlast) taz_chudziak_scalenie)
  (command "_solid" taz_chudziak_p1 taz_chudziak_p2 taz_chudziak_p4 taz_chudziak_p3 "")
  (ssadd (entlast) taz_chudziak_scalenie)
  (command "_ZOOM" "_SCALE" "0.0001X")
  (command "_group" "_C" "*" "" taz_chudziak_scalenie "")
  (setq taz_chudziak_scalenie (ssadd))
  (command "_UCS" "_P")
  (command "_layer" "_S" taz_aktualna_warstwa "")
  (setvar "orthomode" taz_aktualny_tryb_orto)
  (princ)
)

(defun taz_batting( / *error* )
  (defun *error* ( taz_przyczyna_bledu )
    (command)(command)
    (setq taz_batting_scalenie (ssadd))
    (command "_layer" "_S" taz_aktualna_warstwa "")
    (setvar "CELTYPE" taz_aktualny_styl_linii)
    (setvar "CELTSCALE" taz_aktualna_skala_rodzaju_linii)
    (princ)
  )
  (setq taz_aktualna_warstwa (getvar "CLAYER"))
  (setq taz_aktualny_styl_linii (getvar "CELTYPE"))
  (setq taz_aktualna_skala_rodzaju_linii (getvar "CELTSCALE"))
  (if (tblsearch "LTYPE" "BATTING")
    (princ)
    (command "_linetype" "_L" "BATTING" "acadiso.lin" "")
  )
  (setq taz_batting_grubosc (getreal "\nPodaj grubosc izolacji (mm): "))
  (command "_layer" "_S" "TAZ_THIN" "")
  (setvar "CELTYPE" "BATTING")
  (setvar "CELTSCALE" (/ taz_batting_grubosc 20))
  (setq taz_batting_scalenie (ssadd))
  (setq taz_batting_p1 (getpoint "\nWskaz poczatkowy punkt wzoru ocieplenia: "))
  (repeat 100
    (setq taz_batting_p2 (getpoint taz_batting_p1 "\nWskaz kolejny punkt wzoru ocieplenia: "))
    (command "_pline" taz_batting_p1 taz_batting_p2 "")
    (ssadd (entlast) taz_batting_scalenie)
    (command "_pedit" "_M" taz_batting_scalenie "" "_J" "" "")
    (setq taz_batting_p1 taz_batting_p2)
  )
  (setq taz_batting_scalenie (ssadd))
  (command "_layer" "_S" taz_aktualna_warstwa "")
  (setvar "CELTYPE" taz_aktualny_styl_linii)
  (setvar "CELTSCALE" taz_aktualna_skala_rodzaju_linii)
  (princ)
)

(defun taz_formatka( / *error* )
  (defun *error* ( taz_przyczyna_bledu )
    (command)(command)
    (setq taz_formatka_scalenie (ssadd))
    (command "_layer" "_S" taz_aktualna_warstwa "")
    (princ)
  )
  (setq taz_aktualna_warstwa (getvar "CLAYER"))
  (command "_layer" "_S" "TAZ_THIN" "")
  (new_dialog "taz_formatka_okno" (load_dialog "C:\\TAZ\\DCL\\taz_formatka.DCL"))
  (action_tile
    "cancel"
    "(setq taz_formatka_papier_lista nil)
    (setq taz_formatka_papier_wartosc nil)
    (setq taz_formatka_orientacja_lista nil)
    (setq taz_formatka_orientacja_wartosc nil)
    (done_dialog)"
  )
  (action_tile
    "accept"
    "(setq taz_formatka_papier_lista (get_attr \"taz_formatka_papier_dcl\" \"list\"))
    (setq taz_formatka_papier_wartosc (get_tile \"taz_formatka_papier_dcl\"))
    (setq taz_formatka_orientacja_lista (get_attr \"taz_formatka_orientacja_dcl\" \"list\"))
    (setq taz_formatka_orientacja_wartosc (get_tile \"taz_formatka_orientacja_dcl\"))
    (done_dialog)"
  )
  (start_dialog)
  (unload_dialog (load_dialog "C:\\TAZ\\DCL\\taz_formatka.DCL"))
  (while (vl-string-search "\n" taz_formatka_papier_lista)
    (setq taz_formatka_papier_lista (vl-string-subst " " "\n" taz_formatka_papier_lista))
  )
  (while (vl-string-search "\n" taz_formatka_orientacja_lista)
    (setq taz_formatka_orientacja_lista (vl-string-subst " " "\n" taz_formatka_orientacja_lista))
  )
  (setq taz_formatka_papier (nth (atoi taz_formatka_papier_wartosc) (taz_lista taz_formatka_papier_lista)))
  (setq taz_formatka_orientacja (nth (atoi taz_formatka_orientacja_wartosc) (taz_lista taz_formatka_orientacja_lista)))
  (if (equal taz_formatka_papier "A4")
    (if (equal taz_formatka_orientacja "Poziomo")
      (progn
        ;ZEWNETRZNA RAMKA
        (setq taz_formatka_p1 (getpoint "\nWskaz punkt wstawienia ramki rysunkowej: "))
        (setq taz_formatka_p2 (subst (- (car taz_formatka_p1) 148.5) (car taz_formatka_p1) taz_formatka_p1))
        (setq taz_formatka_p2 (subst (- (cadr taz_formatka_p1) 105) (cadr taz_formatka_p1) taz_formatka_p2))
        (setq taz_formatka_p2 (list (car taz_formatka_p2) (cadr taz_formatka_p2)))
        (setq taz_formatka_p3 (subst (+ (car taz_formatka_p1) 148.5) (car taz_formatka_p1) taz_formatka_p1))
        (setq taz_formatka_p3 (subst (+ (cadr taz_formatka_p1) 105) (cadr taz_formatka_p1) taz_formatka_p3))
        (setq taz_formatka_p3 (list (car taz_formatka_p3) (cadr taz_formatka_p3)))
        ;WEWNETRZNA RAMKA
        (setq taz_formatka_p4 (subst (- (car taz_formatka_p1) 118.5) (car taz_formatka_p1) taz_formatka_p1))
        (setq taz_formatka_p4 (subst (- (cadr taz_formatka_p1) 95) (cadr taz_formatka_p1) taz_formatka_p4))
        (setq taz_formatka_p4 (list (car taz_formatka_p4) (cadr taz_formatka_p4)))
        (setq taz_formatka_p5 (subst (+ (car taz_formatka_p1) 138.5) (car taz_formatka_p1) taz_formatka_p1))
        (setq taz_formatka_p5 (subst (+ (cadr taz_formatka_p1) 95) (cadr taz_formatka_p1) taz_formatka_p5))
        (setq taz_formatka_p5 (list (car taz_formatka_p5) (cadr taz_formatka_p5)))
      )
      (progn
        ;ZEWNETRZNA RAMKA
        (setq taz_formatka_p1 (getpoint "\nWskaz punkt wstawienia ramki rysunkowej: "))
        (setq taz_formatka_p2 (subst (- (car taz_formatka_p1) 105) (car taz_formatka_p1) taz_formatka_p1))
        (setq taz_formatka_p2 (subst (- (cadr taz_formatka_p1) 148.5) (cadr taz_formatka_p1) taz_formatka_p2))
        (setq taz_formatka_p2 (list (car taz_formatka_p2) (cadr taz_formatka_p2)))
        (setq taz_formatka_p3 (subst (+ (car taz_formatka_p1) 105) (car taz_formatka_p1) taz_formatka_p1))
        (setq taz_formatka_p3 (subst (+ (cadr taz_formatka_p1) 148.5) (cadr taz_formatka_p1) taz_formatka_p3))
        (setq taz_formatka_p3 (list (car taz_formatka_p3) (cadr taz_formatka_p3)))
        ;WEWNETRZNA RAMKA
        (setq taz_formatka_p4 (subst (- (car taz_formatka_p1) 75) (car taz_formatka_p1) taz_formatka_p1))
        (setq taz_formatka_p4 (subst (- (cadr taz_formatka_p1) 138.5) (cadr taz_formatka_p1) taz_formatka_p4))
        (setq taz_formatka_p4 (list (car taz_formatka_p4) (cadr taz_formatka_p4)))
        (setq taz_formatka_p5 (subst (+ (car taz_formatka_p1) 95) (car taz_formatka_p1) taz_formatka_p1))
        (setq taz_formatka_p5 (subst (+ (cadr taz_formatka_p1) 138.5) (cadr taz_formatka_p1) taz_formatka_p5))
        (setq taz_formatka_p5 (list (car taz_formatka_p5) (cadr taz_formatka_p5)))
      )
    )
    (princ)
  )
  (if (equal taz_formatka_papier "A3")
    (if (equal taz_formatka_orientacja "Poziomo")
      (progn
        ;ZEWNETRZNA RAMKA
        (setq taz_formatka_p1 (getpoint "\nWskaz punkt wstawienia ramki rysunkowej: "))
        (setq taz_formatka_p2 (subst (- (car taz_formatka_p1) 210) (car taz_formatka_p1) taz_formatka_p1))
        (setq taz_formatka_p2 (subst (- (cadr taz_formatka_p1) 148.5) (cadr taz_formatka_p1) taz_formatka_p2))
        (setq taz_formatka_p2 (list (car taz_formatka_p2) (cadr taz_formatka_p2)))
        (setq taz_formatka_p3 (subst (+ (car taz_formatka_p1) 210) (car taz_formatka_p1) taz_formatka_p1))
        (setq taz_formatka_p3 (subst (+ (cadr taz_formatka_p1) 148.5) (cadr taz_formatka_p1) taz_formatka_p3))
        (setq taz_formatka_p3 (list (car taz_formatka_p3) (cadr taz_formatka_p3)))
        ;WEWNETRZNA RAMKA
        (setq taz_formatka_p4 (subst (- (car taz_formatka_p1) 180) (car taz_formatka_p1) taz_formatka_p1))
        (setq taz_formatka_p4 (subst (- (cadr taz_formatka_p1) 138.5) (cadr taz_formatka_p1) taz_formatka_p4))
        (setq taz_formatka_p4 (list (car taz_formatka_p4) (cadr taz_formatka_p4)))
        (setq taz_formatka_p5 (subst (+ (car taz_formatka_p1) 200) (car taz_formatka_p1) taz_formatka_p1))
        (setq taz_formatka_p5 (subst (+ (cadr taz_formatka_p1) 138.5) (cadr taz_formatka_p1) taz_formatka_p5))
        (setq taz_formatka_p5 (list (car taz_formatka_p5) (cadr taz_formatka_p5)))
      )
      (progn
        ;ZEWNETRZNA RAMKA
        (setq taz_formatka_p1 (getpoint "\nWskaz punkt wstawienia ramki rysunkowej: "))
        (setq taz_formatka_p2 (subst (- (car taz_formatka_p1) 148.5) (car taz_formatka_p1) taz_formatka_p1))
        (setq taz_formatka_p2 (subst (- (cadr taz_formatka_p1) 210) (cadr taz_formatka_p1) taz_formatka_p2))
        (setq taz_formatka_p2 (list (car taz_formatka_p2) (cadr taz_formatka_p2)))
        (setq taz_formatka_p3 (subst (+ (car taz_formatka_p1) 148.5) (car taz_formatka_p1) taz_formatka_p1))
        (setq taz_formatka_p3 (subst (+ (cadr taz_formatka_p1) 210) (cadr taz_formatka_p1) taz_formatka_p3))
        (setq taz_formatka_p3 (list (car taz_formatka_p3) (cadr taz_formatka_p3)))
        ;WEWNETRZNA RAMKA
        (setq taz_formatka_p4 (subst (- (car taz_formatka_p1) 118.5) (car taz_formatka_p1) taz_formatka_p1))
        (setq taz_formatka_p4 (subst (- (cadr taz_formatka_p1) 200) (cadr taz_formatka_p1) taz_formatka_p4))
        (setq taz_formatka_p4 (list (car taz_formatka_p4) (cadr taz_formatka_p4)))
        (setq taz_formatka_p5 (subst (+ (car taz_formatka_p1) 138.5) (car taz_formatka_p1) taz_formatka_p1))
        (setq taz_formatka_p5 (subst (+ (cadr taz_formatka_p1) 200) (cadr taz_formatka_p1) taz_formatka_p5))
        (setq taz_formatka_p5 (list (car taz_formatka_p5) (cadr taz_formatka_p5)))
      )
    )
    (princ)
  )
  (if (equal taz_formatka_papier "A2")
    (if (equal taz_formatka_orientacja "Poziomo")
      (progn
        ;ZEWNETRZNA RAMKA
        (setq taz_formatka_p1 (getpoint "\nWskaz punkt wstawienia ramki rysunkowej: "))
        (setq taz_formatka_p2 (subst (- (car taz_formatka_p1) 297) (car taz_formatka_p1) taz_formatka_p1))
        (setq taz_formatka_p2 (subst (- (cadr taz_formatka_p1) 210) (cadr taz_formatka_p1) taz_formatka_p2))
        (setq taz_formatka_p2 (list (car taz_formatka_p2) (cadr taz_formatka_p2)))
        (setq taz_formatka_p3 (subst (+ (car taz_formatka_p1) 297) (car taz_formatka_p1) taz_formatka_p1))
        (setq taz_formatka_p3 (subst (+ (cadr taz_formatka_p1) 210) (cadr taz_formatka_p1) taz_formatka_p3))
        (setq taz_formatka_p3 (list (car taz_formatka_p3) (cadr taz_formatka_p3)))
        ;WEWNETRZNA RAMKA
        (setq taz_formatka_p4 (subst (- (car taz_formatka_p1) 267) (car taz_formatka_p1) taz_formatka_p1))
        (setq taz_formatka_p4 (subst (- (cadr taz_formatka_p1) 200) (cadr taz_formatka_p1) taz_formatka_p4))
        (setq taz_formatka_p4 (list (car taz_formatka_p4) (cadr taz_formatka_p4)))
        (setq taz_formatka_p5 (subst (+ (car taz_formatka_p1) 287) (car taz_formatka_p1) taz_formatka_p1))
        (setq taz_formatka_p5 (subst (+ (cadr taz_formatka_p1) 200) (cadr taz_formatka_p1) taz_formatka_p5))
        (setq taz_formatka_p5 (list (car taz_formatka_p5) (cadr taz_formatka_p5)))
      )
      (progn
        ;ZEWNETRZNA RAMKA
        (setq taz_formatka_p1 (getpoint "\nWskaz punkt wstawienia ramki rysunkowej: "))
        (setq taz_formatka_p2 (subst (- (car taz_formatka_p1) 210) (car taz_formatka_p1) taz_formatka_p1))
        (setq taz_formatka_p2 (subst (- (cadr taz_formatka_p1) 297) (cadr taz_formatka_p1) taz_formatka_p2))
        (setq taz_formatka_p2 (list (car taz_formatka_p2) (cadr taz_formatka_p2)))
        (setq taz_formatka_p3 (subst (+ (car taz_formatka_p1) 210) (car taz_formatka_p1) taz_formatka_p1))
        (setq taz_formatka_p3 (subst (+ (cadr taz_formatka_p1) 297) (cadr taz_formatka_p1) taz_formatka_p3))
        (setq taz_formatka_p3 (list (car taz_formatka_p3) (cadr taz_formatka_p3)))
        ;WEWNETRZNA RAMKA
        (setq taz_formatka_p4 (subst (- (car taz_formatka_p1) 180) (car taz_formatka_p1) taz_formatka_p1))
        (setq taz_formatka_p4 (subst (- (cadr taz_formatka_p1) 287) (cadr taz_formatka_p1) taz_formatka_p4))
        (setq taz_formatka_p4 (list (car taz_formatka_p4) (cadr taz_formatka_p4)))
        (setq taz_formatka_p5 (subst (+ (car taz_formatka_p1) 200) (car taz_formatka_p1) taz_formatka_p1))
        (setq taz_formatka_p5 (subst (+ (cadr taz_formatka_p1) 287) (cadr taz_formatka_p1) taz_formatka_p5))
        (setq taz_formatka_p5 (list (car taz_formatka_p5) (cadr taz_formatka_p5)))
      )
    )
    (princ)
  )
  (if (equal taz_formatka_papier "A1")
    (if (equal taz_formatka_orientacja "Poziomo")
      (progn
        ;ZEWNETRZNA RAMKA
        (setq taz_formatka_p1 (getpoint "\nWskaz punkt wstawienia ramki rysunkowej: "))
        (setq taz_formatka_p2 (subst (- (car taz_formatka_p1) 420.5) (car taz_formatka_p1) taz_formatka_p1))
        (setq taz_formatka_p2 (subst (- (cadr taz_formatka_p1) 297) (cadr taz_formatka_p1) taz_formatka_p2))
        (setq taz_formatka_p2 (list (car taz_formatka_p2) (cadr taz_formatka_p2)))
        (setq taz_formatka_p3 (subst (+ (car taz_formatka_p1) 420.5) (car taz_formatka_p1) taz_formatka_p1))
        (setq taz_formatka_p3 (subst (+ (cadr taz_formatka_p1) 297) (cadr taz_formatka_p1) taz_formatka_p3))
        (setq taz_formatka_p3 (list (car taz_formatka_p3) (cadr taz_formatka_p3)))
        ;WEWNETRZNA RAMKA
        (setq taz_formatka_p4 (subst (- (car taz_formatka_p1) 390.5) (car taz_formatka_p1) taz_formatka_p1))
        (setq taz_formatka_p4 (subst (- (cadr taz_formatka_p1) 287) (cadr taz_formatka_p1) taz_formatka_p4))
        (setq taz_formatka_p4 (list (car taz_formatka_p4) (cadr taz_formatka_p4)))
        (setq taz_formatka_p5 (subst (+ (car taz_formatka_p1) 410.5) (car taz_formatka_p1) taz_formatka_p1))
        (setq taz_formatka_p5 (subst (+ (cadr taz_formatka_p1) 287) (cadr taz_formatka_p1) taz_formatka_p5))
        (setq taz_formatka_p5 (list (car taz_formatka_p5) (cadr taz_formatka_p5)))
      )
      (progn
        ;ZEWNETRZNA RAMKA
        (setq taz_formatka_p1 (getpoint "\nWskaz punkt wstawienia ramki rysunkowej: "))
        (setq taz_formatka_p2 (subst (- (car taz_formatka_p1) 297) (car taz_formatka_p1) taz_formatka_p1))
        (setq taz_formatka_p2 (subst (- (cadr taz_formatka_p1) 420.5) (cadr taz_formatka_p1) taz_formatka_p2))
        (setq taz_formatka_p2 (list (car taz_formatka_p2) (cadr taz_formatka_p2)))
        (setq taz_formatka_p3 (subst (+ (car taz_formatka_p1) 297) (car taz_formatka_p1) taz_formatka_p1))
        (setq taz_formatka_p3 (subst (+ (cadr taz_formatka_p1) 420.5) (cadr taz_formatka_p1) taz_formatka_p3))
        (setq taz_formatka_p3 (list (car taz_formatka_p3) (cadr taz_formatka_p3)))
        ;WEWNETRZNA RAMKA
        (setq taz_formatka_p4 (subst (- (car taz_formatka_p1) 267) (car taz_formatka_p1) taz_formatka_p1))
        (setq taz_formatka_p4 (subst (- (cadr taz_formatka_p1) 410.5) (cadr taz_formatka_p1) taz_formatka_p4))
        (setq taz_formatka_p4 (list (car taz_formatka_p4) (cadr taz_formatka_p4)))
        (setq taz_formatka_p5 (subst (+ (car taz_formatka_p1) 287) (car taz_formatka_p1) taz_formatka_p1))
        (setq taz_formatka_p5 (subst (+ (cadr taz_formatka_p1) 410.5) (cadr taz_formatka_p1) taz_formatka_p5))
        (setq taz_formatka_p5 (list (car taz_formatka_p5) (cadr taz_formatka_p5)))
      )
    )
    (princ)
  )
  (if (equal taz_formatka_papier "A0")
    (if (equal taz_formatka_orientacja "Poziomo")
      (progn
        ;ZEWNETRZNA RAMKA
        (setq taz_formatka_p1 (getpoint "\nWskaz punkt wstawienia ramki rysunkowej: "))
        (setq taz_formatka_p2 (subst (- (car taz_formatka_p1) 594.5) (car taz_formatka_p1) taz_formatka_p1))
        (setq taz_formatka_p2 (subst (- (cadr taz_formatka_p1) 420.5) (cadr taz_formatka_p1) taz_formatka_p2))
        (setq taz_formatka_p2 (list (car taz_formatka_p2) (cadr taz_formatka_p2)))
        (setq taz_formatka_p3 (subst (+ (car taz_formatka_p1) 594.5) (car taz_formatka_p1) taz_formatka_p1))
        (setq taz_formatka_p3 (subst (+ (cadr taz_formatka_p1) 420.5) (cadr taz_formatka_p1) taz_formatka_p3))
        (setq taz_formatka_p3 (list (car taz_formatka_p3) (cadr taz_formatka_p3)))
        ;WEWNETRZNA RAMKA
        (setq taz_formatka_p4 (subst (- (car taz_formatka_p1) 564.5) (car taz_formatka_p1) taz_formatka_p1))
        (setq taz_formatka_p4 (subst (- (cadr taz_formatka_p1) 410.5) (cadr taz_formatka_p1) taz_formatka_p4))
        (setq taz_formatka_p4 (list (car taz_formatka_p4) (cadr taz_formatka_p4)))
        (setq taz_formatka_p5 (subst (+ (car taz_formatka_p1) 584.5) (car taz_formatka_p1) taz_formatka_p1))
        (setq taz_formatka_p5 (subst (+ (cadr taz_formatka_p1) 410.5) (cadr taz_formatka_p1) taz_formatka_p5))
        (setq taz_formatka_p5 (list (car taz_formatka_p5) (cadr taz_formatka_p5)))
      )
      (progn
        ;ZEWNETRZNA RAMKA
        (setq taz_formatka_p1 (getpoint "\nWskaz punkt wstawienia ramki rysunkowej: "))
        (setq taz_formatka_p2 (subst (- (car taz_formatka_p1) 420.5) (car taz_formatka_p1) taz_formatka_p1))
        (setq taz_formatka_p2 (subst (- (cadr taz_formatka_p1) 594.5) (cadr taz_formatka_p1) taz_formatka_p2))
        (setq taz_formatka_p2 (list (car taz_formatka_p2) (cadr taz_formatka_p2)))
        (setq taz_formatka_p3 (subst (+ (car taz_formatka_p1) 420.5) (car taz_formatka_p1) taz_formatka_p1))
        (setq taz_formatka_p3 (subst (+ (cadr taz_formatka_p1) 594.5) (cadr taz_formatka_p1) taz_formatka_p3))
        (setq taz_formatka_p3 (list (car taz_formatka_p3) (cadr taz_formatka_p3)))
        ;WEWNETRZNA RAMKA
        (setq taz_formatka_p4 (subst (- (car taz_formatka_p1) 390.5) (car taz_formatka_p1) taz_formatka_p1))
        (setq taz_formatka_p4 (subst (- (cadr taz_formatka_p1) 584.5) (cadr taz_formatka_p1) taz_formatka_p4))
        (setq taz_formatka_p4 (list (car taz_formatka_p4) (cadr taz_formatka_p4)))
        (setq taz_formatka_p5 (subst (+ (car taz_formatka_p1) 410.5) (car taz_formatka_p1) taz_formatka_p1))
        (setq taz_formatka_p5 (subst (+ (cadr taz_formatka_p1) 584.5) (cadr taz_formatka_p1) taz_formatka_p5))
        (setq taz_formatka_p5 (list (car taz_formatka_p5) (cadr taz_formatka_p5)))
      )
    )
    (princ)
  )
  (setq taz_formatka_scalenie (ssadd))
  (command "_ZOOM" "_SCALE" "10000X")
  (command "_rectang" taz_formatka_p2 taz_formatka_p3)
  (ssadd (entlast) taz_formatka_scalenie)
  (command "_rectang" taz_formatka_p4 taz_formatka_p5)
  (ssadd (entlast) taz_formatka_scalenie)
  (command "_ZOOM" "_SCALE" "0.0001X")
  (command "_group" "_C" "*" "" taz_formatka_scalenie "")
  (setq taz_formatka_scalenie (ssadd))
  (command "_layer" "_S" taz_aktualna_warstwa "")
  (princ)
)

(defun taz_symbol_otworu_prostokatnego( / *error* )
  (defun *error* ( taz_przyczyna_bledu )
    (command)(command)
    (setq taz_symbol_otworu_prostokatnego_pomoc_scalenie (ssadd))
    (command "_UCS" "_P")
    (command "_layer" "_S" taz_aktualna_warstwa "")
    (princ)
  )
  (command "_UCS" "_W")
  (setq taz_aktualna_warstwa (getvar "CLAYER"))
  (command "_layer" "_S" "TAZ_HATCH" "")
  (setq taz_symbol_otworu_prostokatnego_p1 (getpoint "\nWskaz pierwszy punkt przekatnej otworu: "))
  (setq taz_symbol_otworu_prostokatnego_p2 (getcorner taz_symbol_otworu_prostokatnego_p1 "\nWskaz drugi punkt przekatnej otworu: "))
  (setq taz_symbol_otworu_prostokatnego_p3 (list (min (car taz_symbol_otworu_prostokatnego_p1) (car taz_symbol_otworu_prostokatnego_p2)) (min (cadr taz_symbol_otworu_prostokatnego_p2) (cadr taz_symbol_otworu_prostokatnego_p1)) (caddr taz_symbol_otworu_prostokatnego_p1)))
  (setq taz_symbol_otworu_prostokatnego_p4 (list (max (car taz_symbol_otworu_prostokatnego_p1) (car taz_symbol_otworu_prostokatnego_p2)) (max (cadr taz_symbol_otworu_prostokatnego_p2) (cadr taz_symbol_otworu_prostokatnego_p1)) (caddr taz_symbol_otworu_prostokatnego_p1)))
  (setq taz_symbol_otworu_prostokatnego_p5 (list (car taz_symbol_otworu_prostokatnego_p3) (cadr taz_symbol_otworu_prostokatnego_p4) (caddr taz_symbol_otworu_prostokatnego_p3)))
  (setq taz_symbol_otworu_prostokatnego_pomoc_scalenie (ssadd))
  (command "_ZOOM" "_SCALE" "10000X")
  (command "_pline" taz_symbol_otworu_prostokatnego_p3 taz_symbol_otworu_prostokatnego_p4 "")
  (ssadd (entlast) taz_symbol_otworu_prostokatnego_pomoc_scalenie)
  (command "_ZOOM" "_SCALE" "0.0001X")
  (setq taz_symbol_otworu_prostokatnego_a1 (angle taz_symbol_otworu_prostokatnego_p3 taz_symbol_otworu_prostokatnego_p4))
  (setq taz_symbol_otworu_prostokatnego_odleglosc1 (/ (distance taz_symbol_otworu_prostokatnego_p3 taz_symbol_otworu_prostokatnego_p4) 2))
  (setq taz_symbol_otworu_prostokatnego_p6 (polar taz_symbol_otworu_prostokatnego_p3 taz_symbol_otworu_prostokatnego_a1 taz_symbol_otworu_prostokatnego_odleglosc1))
  (command "_pline" taz_symbol_otworu_prostokatnego_p5 (osnap taz_symbol_otworu_prostokatnego_p6 "_per") "")
  (setq taz_symbol_otworu_prostokatnego_p7 (list (cadr (assoc 10 (reverse (entget (entlast))))) (caddr (assoc 10 (reverse (entget (entlast))))) (caddr taz_symbol_otworu_prostokatnego_p5)))
  (ssadd (entlast) taz_symbol_otworu_prostokatnego_pomoc_scalenie)
  (setq taz_symbol_otworu_prostokatnego_a2 (angle taz_symbol_otworu_prostokatnego_p5 taz_symbol_otworu_prostokatnego_p7))
  (setq taz_symbol_otworu_prostokatnego_odleglosc2 (/ (distance taz_symbol_otworu_prostokatnego_p5 taz_symbol_otworu_prostokatnego_p7) 2))
  (setq taz_symbol_otworu_prostokatnego_p8 (polar taz_symbol_otworu_prostokatnego_p5 taz_symbol_otworu_prostokatnego_a2 taz_symbol_otworu_prostokatnego_odleglosc2))
  (command "_erase" taz_symbol_otworu_prostokatnego_pomoc_scalenie "")
  (command "_ZOOM" "_SCALE" "10000X")
  (command "_solid" taz_symbol_otworu_prostokatnego_p3 taz_symbol_otworu_prostokatnego_p5 taz_symbol_otworu_prostokatnego_p8 taz_symbol_otworu_prostokatnego_p4 "")
  (command "_draworder" (entlast) "" "_B")
  (command "_ZOOM" "_SCALE" "0.0001X")
  (setq taz_symbol_otworu_prostokatnego_pomoc_scalenie (ssadd))
  (command "_UCS" "_P")
  (command "_layer" "_S" taz_aktualna_warstwa "")
  (princ)
)

(defun taz_symbol_otworu_okraglego( / *error* )
  (defun *error* ( taz_przyczyna_bledu )
    (command)(command)
    (setq taz_symbol_otworu_okraglego_pomoc_scalenie (ssadd))
    (command "_UCS" "_P")
    (command "_layer" "_S" taz_aktualna_warstwa "")
    (setvar "OSMODE" taz_aktualny_tryb_przyciagania)
    (princ)
  )
  (command "_UCS" "_W")
  (setq taz_aktualna_warstwa (getvar "CLAYER"))
  (command "_layer" "_S" "TAZ_HATCH" "")
  (setq taz_aktualny_tryb_przyciagania (getvar "OSMODE"))
  (setq taz_aktualny_styl_kreskowania (getvar "HPNAME"))
  (setvar "OSMODE" 4)
  (setq taz_symbol_otworu_okraglego_p1 (getpoint "\nWskaz srodek otworu: "))
  (setvar "OSMODE" 512)
  (setq taz_symbol_otworu_okraglego_p2 (getpoint taz_symbol_otworu_okraglego_p1 "\nWskaz krawedz otworu: "))
  (setvar "OSMODE" taz_aktualny_tryb_przyciagania)
  (setq taz_symbol_otworu_okraglego_odleglosc1 (distance taz_symbol_otworu_okraglego_p1 taz_symbol_otworu_okraglego_p2))
  (setq taz_symbol_otworu_okraglego_odleglosc2 (/ (distance taz_symbol_otworu_okraglego_p1 taz_symbol_otworu_okraglego_p2) 2))
  (setq taz_symbol_otworu_okraglego_p3 (polar taz_symbol_otworu_okraglego_p1 (/ 135 (/ 180 PI)) taz_symbol_otworu_okraglego_odleglosc1))
  (setq taz_symbol_otworu_okraglego_p4 (polar taz_symbol_otworu_okraglego_p1 (/ 225 (/ 180 PI)) taz_symbol_otworu_okraglego_odleglosc1))
  (setq taz_symbol_otworu_okraglego_p5 (polar taz_symbol_otworu_okraglego_p1 (/ 45 (/ 180 PI)) taz_symbol_otworu_okraglego_odleglosc1))
  (setq taz_symbol_otworu_okraglego_p6 (polar taz_symbol_otworu_okraglego_p1 (/ 135 (/ 180 PI)) taz_symbol_otworu_okraglego_odleglosc2))
  (setq taz_symbol_otworu_okraglego_pomoc_scalenie (ssadd))
  (command "_ZOOM" "_SCALE" "10000X")
  (command "_arc" taz_symbol_otworu_okraglego_p4 taz_symbol_otworu_okraglego_p6 taz_symbol_otworu_okraglego_p5)
  (ssadd (entlast) taz_symbol_otworu_okraglego_pomoc_scalenie)
  (command "_arc" taz_symbol_otworu_okraglego_p4 taz_symbol_otworu_okraglego_p3 taz_symbol_otworu_okraglego_p5)
  (ssadd (entlast) taz_symbol_otworu_okraglego_pomoc_scalenie)
  (command "_hatch" "_S" taz_symbol_otworu_okraglego_pomoc_scalenie "")
  (command "_draworder" (entlast) "" "_B")
  (command "_ZOOM" "_SCALE" "0.0001X")
  (command "_erase" taz_symbol_otworu_okraglego_pomoc_scalenie "")
  (setq taz_symbol_otworu_okraglego_pomoc_scalenie (ssadd))
  (setvar "HPNAME" taz_aktualny_styl_kreskowania)
  (command "_UCS" "_P")
  (command "_layer" "_S" taz_aktualna_warstwa "")
  (princ)
)
