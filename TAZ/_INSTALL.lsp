(defun taz_instalacja()
  (if (equal (vl-string-search ";C:\\taz\\icons" (vla-get-SupportPath (vla-get-files  (vla-get-preferences (vlax-get-Acad-object))))) nil)
    (vla-put-SupportPath (vla-get-files  (vla-get-preferences (vlax-get-Acad-object))) (strcat (vla-get-SupportPath (vla-get-files  (vla-get-preferences (vlax-get-Acad-object)))) ";C:\\taz\\icons"))
    (princ)
  )
  (if (equal (findfile (strcat (vla-get-PrinterStyleSheetPath (vla-get-files  (vla-get-preferences (vlax-get-Acad-object)))) "\\taz.ctb")) nil)
    (vl-file-copy "C:\\TAZ\\STYLES\\taz.ctb" (strcat (vla-get-PrinterStyleSheetPath (vla-get-files  (vla-get-preferences (vlax-get-Acad-object)))) "\\taz.ctb"))
    (princ)
  )
)
(taz_instalacja)
(vla-load (vla-get-menugroups (vlax-get-acad-object)) "C:\\TAZ\\taz.cuix")
(command "-TOOLBAR" "TAZ" "Float" "400,210" "1")
(princ "\n########## ZAINSTALOWANO TOOLBAR AZ ##########")
(princ)
