(defun taz_dezinstalacja()
  (if (equal (vl-string-search ";C:\\taz\\icons" (vla-get-SupportPath (vla-get-files  (vla-get-preferences (vlax-get-Acad-object))))) nil)
    (princ)
    (vla-put-SupportPath (vla-get-files  (vla-get-preferences (vlax-get-Acad-object))) (vl-string-subst "" ";C:\\taz\\icons" (vla-get-SupportPath (vla-get-files  (vla-get-preferences (vlax-get-Acad-object))))))
  )
  (if (equal (findfile (strcat (vla-get-PrinterStyleSheetPath (vla-get-files  (vla-get-preferences (vlax-get-Acad-object)))) "\\taz.ctb")) nil)
    (princ)
    (vl-file-delete (strcat (vla-get-PrinterStyleSheetPath (vla-get-files  (vla-get-preferences (vlax-get-Acad-object)))) "\\taz.ctb"))
  )
)
(taz_dezinstalacja)
(command "CUIUNLOAD" "TAZ")
(princ "\n########## ODINSTALOWANO TOOLBAR AZ ##########")
(princ)
